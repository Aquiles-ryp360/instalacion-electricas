(vl-load-com)
(setq doc (vla-get-ActiveDocument (vlax-get-acad-object)))
(princ "\nDOC=")
(princ doc)
(princ "\nLAYOUTS=")
(princ (if doc (vla-get-Layouts doc) "NO-DOC"))
(if doc
  (vlax-for item (vla-get-Layouts doc)
    (princ "\nLAYOUT-NAME=")
    (princ (vla-get-Name item))
  )
)
(setq layout (vla-Item (vla-get-Layouts doc) "Model"))
(vla-put-ConfigName layout "DWG To PDF.pc3")
(vla-RefreshPlotDeviceInfo layout)
(vla-put-CanonicalMediaName layout "ISO_full_bleed_A3_(420.00_x_297.00_MM)")
(vla-put-PaperUnits layout 1)
(vla-put-PlotRotation layout 1)
(vla-put-PlotType layout 1)
(vla-put-UseStandardScale layout :vlax-true)
(vla-put-StandardScale layout 0)
(vla-put-CenterPlot layout :vlax-true)
(vla-put-PlotWithPlotStyles layout :vlax-true)
(vla-put-StyleSheet layout "monochrome.ctb")
(vla-put-PlotHidden layout :vlax-false)
(vla-Regen doc 1)
(vla-PlotToFile
  (vla-get-Plot doc)
  "C:/Users/renzo/instalacion-electricas/latex/planos/AVANCE DEL PLANO ELECTRICO1.pdf"
  "DWG To PDF.pc3"
)
(vla-Close doc :vlax-false)
